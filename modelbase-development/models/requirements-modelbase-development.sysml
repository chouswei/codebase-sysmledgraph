/*
  Model-based development workflow: four domains, plan from modelbase, report from
  implement side (per-domain names: e.g. codebase for software, hardware repo,
  mechanism repo, deployment repo). Iteration, traceability.
*/
package ModelbaseDevelopmentRequirements {

  requirement def ReqFourDomains {
    doc /*
      The model-based development workflow shall include the four development domains:
      software development, hardware development, mechanism development, and system deployment.
    */
  }

  requirement def ReqWorkflowDescribed {
    doc /*
      The workflow shall be described in the model (activities, actions, and their order
      or iteration) so that plan → implement → report → update is explicit.
    */
  }

  requirement def ReqIteration {
    doc /*
      The process shall support iteration: feedback from the implement report (alignment, gaps)
      shall be usable to update the model or plan and to re-run development steps.
    */
  }

  requirement def ReqPlanFromModelbase {
    doc /*
      The plan (to do: development plan, checkable steps, what to build) shall be
      generated by the modelbase and used as the implementation guide by the
      implement side (e.g. codebase, hardware repo, mechanism repo, deployment repo).
    */
  }

  requirement def ReqReportFromImplementSide {
    doc /*
      The implement report (alignment vs plan/model, gaps, traceability) shall be
      generated by the implement side and delivered to the modelbase for each
      iteration. The implement side only gives the report; it does not decide
      whether the iteration is done. Per domain the implement side may be named
      e.g. codebase (software), hardware repo, mechanism repo, deployment repo.
    */
  }

  requirement def ReqDecideByModelbase {
    doc /*
      Only the modelbase shall decide whether an iteration is done (after
      reviewing the implement report). When the modelbase decides done, it
      updates the plan for the next iteration (or closes). When not done,
      the implement side continues with the same or updated plan.
    */
  }

  requirement def ReqTraceability {
    doc /*
      The implement side shall produce traceability from plan steps to implementation
      (e.g. IMPLEMENTATION_PLAN.md: step, plan, implementation paths) as part of the
      implement report. Per domain: codebase, hardware repo, etc.
    */
  }
}
