/*
  Model-based development structure: modelbase, implement side, and four domains.
  Plan and report flow between modelbase and implement side. Per domain the
  implement side may be named e.g. codebase (software), hardware repo,
  mechanism repo, deployment repo.
*/
package ModelbaseDevelopment {
  private import ModelbaseDevelopmentRequirements::*;

  item def DevelopmentPlan {
    doc /* Plan (to do) generated by modelbase; flows to implement side (e.g. codebase) as implementation guide. */
  }

  item def ImplementReport {
    doc /* Implement report (alignment, gaps, traceability) generated by implement side; flows to modelbase. Implement side only delivers it; only modelbase decides if iteration is done. */
  }

  part def ModelRequirements {
    doc /* Requirements pillar of the SysML model: requirement definitions, satisfy/derive/verify. */
  }

  part def ModelStructure {
    doc /* Structure pillar: blocks, parts, connections, ports; deploy and BDD/IBD. */
  }

  part def ModelBehaviour {
    doc /* Behaviour pillar: actions, activities, state machines; workflow and iteration. */
  }

  part def PlanToDo {
    doc /* Development plan (to do): checkable steps, phases, implementation layout (e.g. CODEBASE_STRUCTURE); generated from the model; flows out as DevelopmentPlan item. */
  }

  part def Modelbase {
    doc /*
      Holds the model and the plan; generates the plan (to do); receives implement report.
      Only the modelbase decides whether an iteration is done; when done, updates the plan
      for the next iteration (or closes). Composed of requirements, structure, behaviour,
      and plan artifact.
    */
    part modelRequirements : ModelRequirements;
    part modelStructure : ModelStructure;
    part modelBehaviour : ModelBehaviour;
    part planToDo : PlanToDo;
    satisfy ReqPlanFromModelbase;
    satisfy ReqDecideByModelbase;
  }

  part def ImplementSide {
    doc /*
      Implements against plan and model; produces and delivers the implement report
      (alignment, gaps, traceability). Only gives the report; does not decide if
      iteration is done. Per domain may be named e.g. codebase (software), hardware
      repo, mechanism repo, deployment repo.
    */
    satisfy ReqReportFromImplementSide;
    satisfy ReqTraceability;
  }

  part def SoftwareDevelopment {
    doc /* Software development: design and implementation against the model and plan. */
    satisfy ReqFourDomains;
  }

  part def HardwareDevelopment {
    doc /* Hardware development: electronics/PCBA (BOM, netlists, parts) aligned with the model. */
    satisfy ReqFourDomains;
  }

  part def MechanismDevelopment {
    doc /* Mechanism development: mechanical/mechatronic design and implementation. */
    satisfy ReqFourDomains;
  }

  part def SystemDeployment {
    doc /* System deployment: integration, topology, operational configuration. */
    satisfy ReqFourDomains;
  }

  part def ModelbaseDevelopmentDeployment {
    doc /* Composite: modelbase + implement side + four development domains. Workflow and iteration in behaviour. */
    part modelbase : Modelbase;
    part implementSide : ImplementSide;
    part softwareDevelopment : SoftwareDevelopment;
    part hardwareDevelopment : HardwareDevelopment;
    part mechanismDevelopment : MechanismDevelopment;
    part systemDeployment : SystemDeployment;
    satisfy ReqFourDomains;
  }
}
